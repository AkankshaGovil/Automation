MULTIMEDIA-SYSTEM-CONTROL-PRIVATE DEFINITIONS AUTOMATIC TAGS ::=
BEGIN





IMPORTS
    DataType,
    ModeElement,
    TerminalCapabilitySet
    FROM MULTIMEDIA-SYSTEM-CONTROL;



-- =========================================================
-- H.245 Application msgs
-- =========================================================

H245Configuration ::=   SEQUENCE
{
    masterSlave     MasterSlaveConf     OPTIONAL,
    capabilities        CapabilitiesConf    OPTIONAL,
    channels        SEQUENCE OF ChannelEntry OPTIONAL,
    modes           SEQUENCE OF ModeEntry    OPTIONAL,

    channelsTimeout     INTEGER(0..65535)   OPTIONAL, -- in seconds
    roundTripTimeout    INTEGER(0..65535)   OPTIONAL, -- in seconds
    requestCloseTimeout     INTEGER(0..65535)   OPTIONAL, -- in seconds
    requestModeTimeout  INTEGER(0..65535)   OPTIONAL, -- in seconds
    mediaLoopTimeout    INTEGER(0..65535)   OPTIONAL, -- in seconds
    ...

}



MasterSlaveConf ::=     SEQUENCE
{
    terminalType    INTEGER (0..255),
    manualOperation NULL    OPTIONAL, -- cancel auto-mode
    manualResponse  NULL  OPTIONAL,
    timeout     INTEGER (0..65535) OPTIONAL, -- in seconds
    ...
}


CapabilitiesConf ::=    SEQUENCE
{
    terminalCapabilitySet   TerminalCapabilitySet,
    manualOperation NULL    OPTIONAL, -- cancel auto-mode
    manualResponse  NULL  OPTIONAL,
    timeout     INTEGER (0..65535) OPTIONAL, -- in seconds
    ...
}

ChannelEntry ::= SEQUENCE
{
    name            IA5String (SIZE(1..128)), -- data type name
    dataType        DataType,
    isDynamicPayloadType    NULL OPTIONAL, -- exist for dynamic payload types (as alt. H.261)
    ...
}

ModeEntry ::= SEQUENCE
{
    name            IA5String (SIZE(1..128)), -- data type name
    mode            ModeElement,
    ...
}

END
